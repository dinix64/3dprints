# -*- coding: utf-8 -*-

# Macro Begin: C:\luis\projects\freecad\tutorials\caixa_lidl\caixas\MAC01.FCMacro +++++++++++++++++++++++++++++++++++++++++++++++++
import FreeCAD
import PartDesign
import PartDesignGui
import Sketcher

App.activeDocument().Body.newObject('Sketcher::SketchObject','Sketch001')
App.activeDocument().Sketch001.Support = (App.activeDocument().XY_Plane, [''])
App.activeDocument().Sketch001.MapMode = 'FlatFace'
App.ActiveDocument.recompute()
#Gui.activeDocument().setEdit('Sketch001')
#Gui.activateWorkbench('SketcherWorkbench')
#ActiveSketch = App.ActiveDocument.getObject('Sketch001')
#tv = Show.TempoVis(App.ActiveDocument)
#if ActiveSketch.ViewObject.HideDependent:
#  objs = tv.get_all_dependent(ActiveSketch)
#  objs = filter(lambda x: not x.TypeId.startswith("TechDraw::"), objs)
#  objs = filter(lambda x: not x.TypeId.startswith("Drawing::"), objs)
#  tv.hide(objs)
#if ActiveSketch.ViewObject.ShowSupport:
#  tv.show([ref[0] for ref in ActiveSketch.Support if not ref[0].isDerivedFrom("PartDesign::Plane")])
#if ActiveSketch.ViewObject.ShowLinks:
#  tv.show([ref[0] for ref in ActiveSketch.ExternalGeometry])
#tv.hide(ActiveSketch)
#ActiveSketch.ViewObject.TempoVis = tv
#del(tv)
#
#ActiveSketch = App.ActiveDocument.getObject('Sketch001')
#if ActiveSketch.ViewObject.RestoreCamera:
#  ActiveSketch.ViewObject.TempoVis.saveCamera()
#
geoList = []
geoList.append(Part.LineSegment(App.Vector(-4.115470,1.925771,0),App.Vector(-5.909824,1.925771,0)))
geoList.append(Part.LineSegment(App.Vector(-5.909824,1.925771,0),App.Vector(-5.909824,3.171851,0)))
geoList.append(Part.LineSegment(App.Vector(-5.909824,3.171851,0),App.Vector(-4.115470,3.171851,0)))
geoList.append(Part.LineSegment(App.Vector(-4.115470,3.171851,0),App.Vector(-4.115470,1.925771,0)))
App.ActiveDocument.Sketch001.addGeometry(geoList,False)
conList = []
conList.append(Sketcher.Constraint('Coincident',0,2,1,1))
conList.append(Sketcher.Constraint('Coincident',1,2,2,1))
conList.append(Sketcher.Constraint('Coincident',2,2,3,1))
conList.append(Sketcher.Constraint('Coincident',3,2,0,1))
conList.append(Sketcher.Constraint('Horizontal',0))
conList.append(Sketcher.Constraint('Horizontal',2))
conList.append(Sketcher.Constraint('Vertical',1))
conList.append(Sketcher.Constraint('Vertical',3))
App.ActiveDocument.Sketch001.addConstraint(conList)

geoList = []
geoList.append(Part.LineSegment(App.Vector(-4.620560,2.758451,0),App.Vector(2.098239,2.758451,0)))
geoList.append(Part.LineSegment(App.Vector(2.098239,2.758451,0),App.Vector(2.098239,-1.563976,0)))
geoList.append(Part.LineSegment(App.Vector(2.098239,-1.563976,0),App.Vector(-4.620560,-1.563976,0)))
geoList.append(Part.LineSegment(App.Vector(-4.620560,-1.563976,0),App.Vector(-4.620560,2.758451,0)))
App.ActiveDocument.Sketch001.addGeometry(geoList,False)
conList = []
conList.append(Sketcher.Constraint('Coincident',4,2,5,1))
conList.append(Sketcher.Constraint('Coincident',5,2,6,1))
conList.append(Sketcher.Constraint('Coincident',6,2,7,1))
conList.append(Sketcher.Constraint('Coincident',7,2,4,1))
conList.append(Sketcher.Constraint('Horizontal',4))
conList.append(Sketcher.Constraint('Horizontal',6))
conList.append(Sketcher.Constraint('Vertical',5))
conList.append(Sketcher.Constraint('Vertical',7))
App.ActiveDocument.Sketch001.addConstraint(conList)

geoList = []
geoList.append(Part.LineSegment(App.Vector(2.165426,-1.653560,0),App.Vector(-11.227377,-1.653560,0)))
geoList.append(Part.LineSegment(App.Vector(-11.227377,-1.653560,0),App.Vector(-11.227377,2.624075,0)))
geoList.append(Part.LineSegment(App.Vector(-11.227377,2.624075,0),App.Vector(2.165426,2.624075,0)))
geoList.append(Part.LineSegment(App.Vector(2.165426,2.624075,0),App.Vector(2.165426,-1.653560,0)))
App.ActiveDocument.Sketch001.addGeometry(geoList,False)
conList = []
conList.append(Sketcher.Constraint('Coincident',8,2,9,1))
conList.append(Sketcher.Constraint('Coincident',9,2,10,1))
conList.append(Sketcher.Constraint('Coincident',10,2,11,1))
conList.append(Sketcher.Constraint('Coincident',11,2,8,1))
conList.append(Sketcher.Constraint('Horizontal',8))
conList.append(Sketcher.Constraint('Horizontal',10))
conList.append(Sketcher.Constraint('Vertical',9))
conList.append(Sketcher.Constraint('Vertical',11))
App.ActiveDocument.Sketch001.addConstraint(conList)

#Gui.getDocument('Unnamed3').resetEdit()
#ActiveSketch = App.ActiveDocument.getObject('Sketch001')
#tv = ActiveSketch.ViewObject.TempoVis
#if tv:
#  tv.restore()
#ActiveSketch.ViewObject.TempoVis = None
#del(tv)
#
#Gui.activateWorkbench('PartDesignWorkbench')
App.getDocument('Unnamed3').recompute()
App.activeDocument().Body.newObject("PartDesign::Pad","Pad001")
App.activeDocument().Pad001.Profile = App.activeDocument().Sketch001
App.activeDocument().Pad001.Length = 10.0
App.ActiveDocument.recompute()
#Gui.activeDocument().hide("Sketch001")
App.ActiveDocument.recompute()
#Gui.ActiveDocument.Pad001.ShapeColor=Gui.ActiveDocument.Body.ShapeColor
#Gui.ActiveDocument.Pad001.LineColor=Gui.ActiveDocument.Body.LineColor
#Gui.ActiveDocument.Pad001.PointColor=Gui.ActiveDocument.Body.PointColor
#Gui.ActiveDocument.Pad001.Transparency=Gui.ActiveDocument.Body.Transparency
#Gui.ActiveDocument.Pad001.DisplayMode=Gui.ActiveDocument.Body.DisplayMode
#Gui.activeDocument().setEdit('Pad001', 0)
#Gui.Selection.clearSelection()
#Gui.activeDocument().hide("Sketch001")
App.ActiveDocument.Pad001.Length = 10.000000
App.ActiveDocument.Pad001.Length2 = 100.000000
App.ActiveDocument.Pad001.Type = 0
App.ActiveDocument.Pad001.UpToFace = None
App.ActiveDocument.Pad001.Reversed = 0
App.ActiveDocument.Pad001.Midplane = 0
App.ActiveDocument.Pad001.Offset = 0.000000
#Gui.activeDocument().hide("Pad")
App.ActiveDocument.recompute()
#Gui.activeDocument().resetEdit()
App.getDocument("Unnamed").recompute()
App.getDocument("Unnamed1").recompute()
App.getDocument("Unnamed2").recompute()
App.getDocument("Unnamed3").removeObject("Sketch001")
App.getDocument("Unnamed3").recompute()
# Macro End: C:\luis\projects\freecad\tutorials\caixa_lidl\caixas\MAC01.FCMacro +++++++++++++++++++++++++++++++++++++++++++++++++
